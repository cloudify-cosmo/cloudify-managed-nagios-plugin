CLOUDIFY-TEST-MIB DEFINITIONS ::= BEGIN

IMPORTS
  MODULE-IDENTITY, OBJECT-TYPE, NOTIFICATION-TYPE, Counter64, Integer32
    FROM SNMPv2-SMI
  MODULE-COMPLIANCE, OBJECT-GROUP, NOTIFICATION-GROUP
    FROM SNMPv2-CONF
  DisplayString
    FROM SNMPv2-TC
  cloudify
    FROM CLOUDIFY-MIB;

cloudifyTest MODULE-IDENTITY
  LAST-UPDATED "201809051310Z"
  ORGANIZATION "Cloudify Platform Ltd."
  CONTACT-INFO "it@cloudify.co"
  DESCRIPTION
    "Cloudify testing MIB tree. NOT FOR PRODUCTION USE. EXPECT UNANNOUNCED CHANGES."
  REVISION "201809051310Z"
  DESCRIPTION
    "Initial MIB for testing SNMP related functions."
  ::= { cloudify 0 }

cloudifyTestNotifications OBJECT IDENTIFIER ::= { cloudifyTest 0 }
cloudifyTestProperties OBJECT IDENTIFIER ::= { cloudifyTest 1 }
cloudifyTestValues OBJECT IDENTIFIER ::= { cloudifyTest 2 }
cloudifyTestCompliance OBJECT IDENTIFIER ::= { cloudifyTest 1000 }
cloudifyTestGroups OBJECT IDENTIFIER ::= { cloudifyTest 1001 }

--Notifications--
cloudifyTestBasicNotify NOTIFICATION-TYPE
  STATUS current
  DESCRIPTION
    "Test basic notification with no extra details."
  ::= { cloudifyTestNotifications 1 }
cloudifyTestVerboseNotify NOTIFICATION-TYPE
  OBJECTS {
    cloudifyTestNotifyMessage,
    cloudifyTestNotifyTarget
  }
  STATUS current
  DESCRIPTION
    "Test verbose notification with extra details included."
  ::= { cloudifyTestNotifications 2 }

--Shared objects--
cloudifyTestNotifyMessage OBJECT-TYPE
  SYNTAX DisplayString
  MAX-ACCESS read-only
  STATUS current
  DESCRIPTION
    "Message associated with a notification."
  ::= { cloudifyTestProperties 1 }
cloudifyTestNotifyTarget OBJECT-TYPE
  SYNTAX DisplayString
  MAX-ACCESS read-only
  STATUS current
  DESCRIPTION
    "Information about target associated with a notification."
  ::= { cloudifyTestProperties 2 }

--Values--
cloudifyTestInteger OBJECT-TYPE
    SYNTAX Integer32
    MAX-ACCESS  read-only
    STATUS current
    DESCRIPTION
      "An arbitrary integer value."
    ::= { cloudifyTestValues 1 }
cloudifyTestCounter OBJECT-TYPE
    SYNTAX Counter64
    MAX-ACCESS read-only
    STATUS current
    DESCRIPTION
      "An arbitrary counter."
    ::= { cloudifyTestValues 2 }

--Compliance--
cloudifyTestComplianceSpec MODULE-COMPLIANCE
  STATUS current
  DESCRIPTION
    "Objects requires to claim compliance with cloudify test SNMP implementation."
  MODULE
    MANDATORY-GROUPS {
      cloudifyTestNotifyGroup,
      cloudifyTestPropertiesGroup,
      cloudifyTestValuesGroup
    }
  ::= { cloudifyTestCompliance 1 }

--Compliance group--
cloudifyTestNotifyGroup NOTIFICATION-GROUP
  NOTIFICATIONS {
    cloudifyTestBasicNotify,
    cloudifyTestVerboseNotify
  }
  STATUS current
  DESCRIPTION
    "Cloudify test notifications"
  ::= { cloudifyTestGroups 1 }
cloudifyTestPropertiesGroup OBJECT-GROUP
  OBJECTS {
    cloudifyTestNotifyMessage,
    cloudifyTestNotifyTarget
  }
  STATUS current
  DESCRIPTION
    "Cloudify test properties"
  ::= { cloudifyTestGroups 2 }
cloudifyTestValuesGroup OBJECT-GROUP
  OBJECTS {
    cloudifyTestInteger,
    cloudifyTestCounter
  }
  STATUS current
  DESCRIPTION
    "Cloudify test values"
  ::= { cloudifyTestGroups 3 }

END
